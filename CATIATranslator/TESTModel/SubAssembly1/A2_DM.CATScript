Language = "VBSCRIPT"

Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim shapeFactory1 As Factory
Set shapeFactory1 = part1.ShapeFactory

Dim reference1 As AnyObject
Set reference1 = originElements1.PlaneYZ

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 0.000000
arrayOfVariantOfDouble1(4) = 1.000000
arrayOfVariantOfDouble1(5) = 0.000000
arrayOfVariantOfDouble1(6) = 0.000000
arrayOfVariantOfDouble1(7) = 0.000000
arrayOfVariantOfDouble1(8) = 1.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(0.000000, 0.000000)

point2D1.ReportName = 1

Dim point2D2 As Point2D
Set point2D2 = factory2D1.CreatePoint(50.000000, 0.000000)

point2D2.ReportName = 2

Dim line2D3 As Line2D
Set line2D3 = factory2D1.CreateLine(0.000000, 0.000000, 50.000000, 0.000000)

line2D3.ReportName = 3

line2D3.StartPoint = point2D1

line2D3.EndPoint = point2D2

Dim point2D3 As Point2D
Set point2D3 = factory2D1.CreatePoint(50.000000, 0.000000)

point2D3.ReportName = 4

Dim point2D4 As Point2D
Set point2D4 = factory2D1.CreatePoint(50.000000, 15.000000)

point2D4.ReportName = 5

Dim line2D4 As Line2D
Set line2D4 = factory2D1.CreateLine(50.000000, 0.000000, 50.000000, 15.000000)

line2D4.ReportName = 6

line2D4.StartPoint = point2D3

line2D4.EndPoint = point2D4

Dim point2D5 As Point2D
Set point2D5 = factory2D1.CreatePoint(50.000000, 15.000000)

point2D5.ReportName = 7

Dim point2D6 As Point2D
Set point2D6 = factory2D1.CreatePoint(10.000000, 15.000000)

point2D6.ReportName = 8

Dim line2D5 As Line2D
Set line2D5 = factory2D1.CreateLine(50.000000, 15.000000, 10.000000, 15.000000)

line2D5.ReportName = 9

line2D5.StartPoint = point2D5

line2D5.EndPoint = point2D6

Dim point2D7 As Point2D
Set point2D7 = factory2D1.CreatePoint(10.000000, 15.000000)

point2D7.ReportName = 10

Dim point2D8 As Point2D
Set point2D8 = factory2D1.CreatePoint(10.000000, 70.000000)

point2D8.ReportName = 11

Dim line2D6 As Line2D
Set line2D6 = factory2D1.CreateLine(10.000000, 15.000000, 10.000000, 70.000000)

line2D6.ReportName = 12

line2D6.StartPoint = point2D7

line2D6.EndPoint = point2D8

Dim point2D9 As Point2D
Set point2D9 = factory2D1.CreatePoint(10.000000, 70.000000)

point2D9.ReportName = 13

Dim point2D10 As Point2D
Set point2D10 = factory2D1.CreatePoint(0.000000, 70.000000)

point2D10.ReportName = 14

Dim line2D7 As Line2D
Set line2D7 = factory2D1.CreateLine(10.000000, 70.000000, 0.000000, 70.000000)

line2D7.ReportName = 15

line2D7.StartPoint = point2D9

line2D7.EndPoint = point2D10

Dim point2D11 As Point2D
Set point2D11 = factory2D1.CreatePoint(0.000000, 70.000000)

point2D11.ReportName = 16

Dim point2D12 As Point2D
Set point2D12 = factory2D1.CreatePoint(0.000000, 0.000000)

point2D12.ReportName = 17

Dim line2D8 As Line2D
Set line2D8 = factory2D1.CreateLine(0.000000, 70.000000, 0.000000, 0.000000)

line2D8.ReportName = 18

line2D8.StartPoint = point2D11

line2D8.EndPoint = point2D12

sketch1.CloseEdition

part1.InWorkObject = sketch1

part1.UpdateObject sketch1

Dim pad1 As Pad
Set pad1 = shapeFactory1.AddNewPad(sketch1, 0.0)

Dim limit1 As Limit
Set limit1 = pad1.FirstLimit

limit1.LimitMode = catOffsetLimit

Dim length1 As Length
Set length1 = limit1.Dimension

length1.Value = 100.000000

Dim limit2 As Limit
Set limit2 = pad1.SecondLimit

limit2.LimitMode = catOffsetLimit

pad1.DirectionOrientation = catRegularOrientation

part1.UpdateObject pad1

Dim reference2 As Reference
Set reference2 = part1.CreateReferenceFromName("Selection_RSur:(Face:(Brp:(Pad.1;0:(Brp:(Sketch.1;18)));None:();Cf11:());Pad.1_ResultOUT;Z0;G3563)")

Dim sketch2 As Sketch
Set sketch2 = sketches1.Add(reference2)

Dim arrayOfVariantOfDouble2(8)
arrayOfVariantOfDouble2(0) = 0.000000
arrayOfVariantOfDouble2(1) = 0.000000
arrayOfVariantOfDouble2(2) = 0.000000
arrayOfVariantOfDouble2(3) = 1.000000
arrayOfVariantOfDouble2(4) = 0.000000
arrayOfVariantOfDouble2(5) = 0.000000
arrayOfVariantOfDouble2(6) = -0.000000
arrayOfVariantOfDouble2(7) = 0.000000
arrayOfVariantOfDouble2(8) = 1.000000
sketch2.SetAbsoluteAxisData arrayOfVariantOfDouble2

part1.InWorkObject = sketch2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D9 As CATBaseDispatch
Set line2D9 = axis2D2.GetItem("HDirection")

line2D9.ReportName = 1

Dim line2D10 As CATBaseDispatch
Set line2D10 = axis2D2.GetItem("VDirection")

line2D10.ReportName = 2

Dim point2D13 As Point2D
Set point2D13 = factory2D2.CreatePoint(50.000000, 55.000000)

point2D13.ReportName = 1

Dim circle2D1 As Circle2D
Set circle2D1 = factory2D2.CreateClosedCircle(50.000000, 55.000000, 5.000000)

circle2D1.ReportName = 2

sketch2.CloseEdition

part1.InWorkObject = sketch2

part1.UpdateObject sketch2

Dim pocket1 As Pocket
Set pocket1 = shapeFactory1.AddNewPocket(sketch2, 0.0)

Dim limit3 As Limit
Set limit3 = pocket1.FirstLimit

limit3.LimitMode = catOffsetLimit

Dim length2 As Length
Set length2 = limit3.Dimension

length2.Value = 10.000000

Dim limit4 As Limit
Set limit4 = pocket1.SecondLimit

limit4.LimitMode = catOffsetLimit

pocket1.DirectionOrientation = catInverseOrientation

part1.UpdateObject pocket1

Dim reference3 As Reference
Set reference3 = part1.CreateReferenceFromName("Selection_RSur:(Face:(Brp:(Pad.1;0:(Brp:(Sketch.1;9)));None:();Cf11:());Pad.1_ResultOUT;Z0;G3563)")

Dim sketch3 As Sketch
Set sketch3 = sketches1.Add(reference3)

Dim arrayOfVariantOfDouble3(8)
arrayOfVariantOfDouble3(0) = 0.000000
arrayOfVariantOfDouble3(1) = 0.000000
arrayOfVariantOfDouble3(2) = 15.000000
arrayOfVariantOfDouble3(3) = 1.000000
arrayOfVariantOfDouble3(4) = 0.000000
arrayOfVariantOfDouble3(5) = 0.000000
arrayOfVariantOfDouble3(6) = 0.000000
arrayOfVariantOfDouble3(7) = 1.000000
arrayOfVariantOfDouble3(8) = -0.000000
sketch3.SetAbsoluteAxisData arrayOfVariantOfDouble3

part1.InWorkObject = sketch3

Dim factory2D3 As Factory2D
Set factory2D3 = sketch3.OpenEdition()

Dim geometricElements3 As GeometricElements
Set geometricElements3 = sketch3.GeometricElements

Dim axis2D3 As GeometricElement
Set axis2D3 = geometricElements3.Item("AbsoluteAxis")

Dim line2D11 As CATBaseDispatch
Set line2D11 = axis2D3.GetItem("HDirection")

line2D11.ReportName = 1

Dim line2D12 As CATBaseDispatch
Set line2D12 = axis2D3.GetItem("VDirection")

line2D12.ReportName = 2

Dim point2D14 As Point2D
Set point2D14 = factory2D3.CreatePoint(50.000000, 25.000000)

point2D14.ReportName = 1

Dim circle2D2 As Circle2D
Set circle2D2 = factory2D3.CreateClosedCircle(50.000000, 25.000000, 5.000000)

circle2D2.ReportName = 2

Dim point2D15 As Point2D
Set point2D15 = factory2D3.CreatePoint(65.000000, 40.000000)

point2D15.ReportName = 3

Dim circle2D3 As Circle2D
Set circle2D3 = factory2D3.CreateClosedCircle(65.000000, 40.000000, 5.000000)

circle2D3.ReportName = 4

Dim point2D16 As Point2D
Set point2D16 = factory2D3.CreatePoint(35.000000, 40.000000)

point2D16.ReportName = 5

Dim circle2D4 As Circle2D
Set circle2D4 = factory2D3.CreateClosedCircle(35.000000, 40.000000, 5.000000)

circle2D4.ReportName = 6

sketch3.CloseEdition

part1.InWorkObject = sketch3

part1.UpdateObject sketch3

Dim pocket2 As Pocket
Set pocket2 = shapeFactory1.AddNewPocket(sketch3, 0.0)

Dim limit5 As Limit
Set limit5 = pocket2.FirstLimit

limit5.LimitMode = catOffsetLimit

Dim length3 As Length
Set length3 = limit5.Dimension

length3.Value = 15.000000

Dim limit6 As Limit
Set limit6 = pocket2.SecondLimit

limit6.LimitMode = catOffsetLimit

pocket2.DirectionOrientation = catInverseOrientation

part1.UpdateObject pocket2

part1.Update

End Sub
