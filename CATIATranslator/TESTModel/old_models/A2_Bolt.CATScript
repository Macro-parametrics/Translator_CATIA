Language = "VBSCRIPT"

Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim shapeFactory1 As Factory
Set shapeFactory1 = part1.ShapeFactory

Dim reference1 As AnyObject
Set reference1 = originElements1.PlaneZX

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = -1.000000
arrayOfVariantOfDouble1(4) = 0.000000
arrayOfVariantOfDouble1(5) = 0.000000
arrayOfVariantOfDouble1(6) = 0.000000
arrayOfVariantOfDouble1(7) = -0.000000
arrayOfVariantOfDouble1(8) = 1.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(0.000000, 0.000000)

point2D1.ReportName = 3

Dim point2D2 As Point2D
Set point2D2 = factory2D1.CreatePoint(7.000000, 0.000000)

point2D2.ReportName = 4

Dim line2D3 As Line2D
Set line2D3 = factory2D1.CreateLine(0.000000, 0.000000, 7.000000, 0.000000)

line2D3.ReportName = 5

line2D3.StartPoint = point2D1

line2D3.EndPoint = point2D2

Dim point2D3 As Point2D
Set point2D3 = factory2D1.CreatePoint(7.000000, 0.000000)

point2D3.ReportName = 6

Dim point2D4 As Point2D
Set point2D4 = factory2D1.CreatePoint(7.000000, 5.000000)

point2D4.ReportName = 7

Dim line2D4 As Line2D
Set line2D4 = factory2D1.CreateLine(7.000000, 0.000000, 7.000000, 5.000000)

line2D4.ReportName = 8

line2D4.StartPoint = point2D3

line2D4.EndPoint = point2D4

Dim point2D5 As Point2D
Set point2D5 = factory2D1.CreatePoint(7.000000, 5.000000)

point2D5.ReportName = 9

Dim point2D6 As Point2D
Set point2D6 = factory2D1.CreatePoint(5.000000, 5.000000)

point2D6.ReportName = 10

Dim line2D5 As Line2D
Set line2D5 = factory2D1.CreateLine(7.000000, 5.000000, 5.000000, 5.000000)

line2D5.ReportName = 11

line2D5.StartPoint = point2D5

line2D5.EndPoint = point2D6

Dim point2D7 As Point2D
Set point2D7 = factory2D1.CreatePoint(5.000000, 5.000000)

point2D7.ReportName = 12

Dim point2D8 As Point2D
Set point2D8 = factory2D1.CreatePoint(5.000000, 50.000000)

point2D8.ReportName = 13

Dim line2D6 As Line2D
Set line2D6 = factory2D1.CreateLine(5.000000, 5.000000, 5.000000, 50.000000)

line2D6.ReportName = 14

line2D6.StartPoint = point2D7

line2D6.EndPoint = point2D8

Dim point2D9 As Point2D
Set point2D9 = factory2D1.CreatePoint(5.000000, 50.000000)

point2D9.ReportName = 15

Dim point2D10 As Point2D
Set point2D10 = factory2D1.CreatePoint(-0.000000, 50.000000)

point2D10.ReportName = 16

Dim line2D7 As Line2D
Set line2D7 = factory2D1.CreateLine(5.000000, 50.000000, -0.000000, 50.000000)

line2D7.ReportName = 17

line2D7.StartPoint = point2D9

line2D7.EndPoint = point2D10

Dim point2D11 As Point2D
Set point2D11 = factory2D1.CreatePoint(0.000000, 50.000000)

point2D11.ReportName = 18

Dim point2D12 As Point2D
Set point2D12 = factory2D1.CreatePoint(0.000000, 0.000000)

point2D12.ReportName = 19

Dim line2D8 As Line2D
Set line2D8 = factory2D1.CreateLine(0.000000, 50.000000, 0.000000, 0.000000)

line2D8.ReportName = 20

line2D8.StartPoint = point2D11

line2D8.EndPoint = point2D12

Dim point2D13 As Point2D
Set point2D13 = factory2D1.CreatePoint(0.000000, 50.000000)

point2D13.ReportName = 21

Dim point2D14 As Point2D
Set point2D14 = factory2D1.CreatePoint(0.000000, 0.000000)

point2D14.ReportName = 22

Dim line2D9 As Line2D
Set line2D9 = factory2D1.CreateLine(0.000000, 50.000000, 0.000000, 0.000000)

sketch1.CenterLine = line2D9 

sketch1.CloseEdition

part1.InWorkObject = sketch1

part1.UpdateObject sketch1

Dim shaft1 As Shaft
Set shaft1 = shapeFactory1.AddNewShaft(sketch1)

Dim angle1 As Angle
Set angle1 = shaft1.FirstAngle

angle1.Value = 360.000000

Dim angle2 As Angle
Set angle2 = shaft1.SecondAngle

angle2.Value = 0.000000

part1.UpdateObject shaft1

Dim reference2 As Reference
Set reference2 = part1.CreateReferenceFromName("Selection_RSur:(Face:(Brp:(Shaft.1;0:(Brp:(Sketch.1;17)));None:();Cf11:());Shaft.1_ResultOUT;Z0;G3563)")

Dim sketch2 As Sketch
Set sketch2 = sketches1.Add(reference2)

Dim arrayOfVariantOfDouble2(8)
arrayOfVariantOfDouble2(0) = 0.000000
arrayOfVariantOfDouble2(1) = 0.000000
arrayOfVariantOfDouble2(2) = 50.000000
arrayOfVariantOfDouble2(3) = 1.000000
arrayOfVariantOfDouble2(4) = 0.000000
arrayOfVariantOfDouble2(5) = -0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D10 As CATBaseDispatch
Set line2D10 = axis2D2.GetItem("HDirection")

line2D10.ReportName = 1

Dim line2D11 As CATBaseDispatch
Set line2D11 = axis2D2.GetItem("VDirection")

line2D11.ReportName = 2

Dim point2D15 As Point2D
Set point2D15 = factory2D2.CreatePoint(-10.000000, 7.000000)

point2D15.ReportName = 3

Dim point2D16 As Point2D
Set point2D16 = factory2D2.CreatePoint(10.000000, 7.000000)

point2D16.ReportName = 4

Dim line2D12 As Line2D
Set line2D12 = factory2D2.CreateLine(-10.000000, 7.000000, 10.000000, 7.000000)

line2D12.ReportName = 5

line2D12.StartPoint = point2D15

line2D12.EndPoint = point2D16

Dim point2D17 As Point2D
Set point2D17 = factory2D2.CreatePoint(10.000000, 7.000000)

point2D17.ReportName = 6

Dim point2D18 As Point2D
Set point2D18 = factory2D2.CreatePoint(10.000000, -7.000000)

point2D18.ReportName = 7

Dim line2D13 As Line2D
Set line2D13 = factory2D2.CreateLine(10.000000, 7.000000, 10.000000, -7.000000)

line2D13.ReportName = 8

line2D13.StartPoint = point2D17

line2D13.EndPoint = point2D18

Dim point2D19 As Point2D
Set point2D19 = factory2D2.CreatePoint(10.000000, -7.000000)

point2D19.ReportName = 9

Dim point2D20 As Point2D
Set point2D20 = factory2D2.CreatePoint(-10.000000, -7.000000)

point2D20.ReportName = 10

Dim line2D14 As Line2D
Set line2D14 = factory2D2.CreateLine(10.000000, -7.000000, -10.000000, -7.000000)

line2D14.ReportName = 11

line2D14.StartPoint = point2D19

line2D14.EndPoint = point2D20

Dim point2D21 As Point2D
Set point2D21 = factory2D2.CreatePoint(-10.000000, -7.000000)

point2D21.ReportName = 12

Dim point2D22 As Point2D
Set point2D22 = factory2D2.CreatePoint(-10.000000, 7.000000)

point2D22.ReportName = 13

Dim line2D15 As Line2D
Set line2D15 = factory2D2.CreateLine(-10.000000, -7.000000, -10.000000, 7.000000)

line2D15.ReportName = 14

line2D15.StartPoint = point2D21

line2D15.EndPoint = point2D22

sketch2.CloseEdition

part1.InWorkObject = sketch2

part1.UpdateObject sketch2

Dim pad1 As Pad
Set pad1 = shapeFactory1.AddNewPad(sketch2, 0.0)

Dim limit1 As Limit
Set limit1 = pad1.FirstLimit

limit1.LimitMode = catOffsetLimit

Dim length1 As Length
Set length1 = limit1.Dimension

length1.Value = 5.000000

Dim limit2 As Limit
Set limit2 = pad1.SecondLimit

limit2.LimitMode = catOffsetLimit

pad1.DirectionOrientation = catRegularOrientation

part1.UpdateObject pad1

part1.Update

End Sub
