Language="VBSCRIPT"

Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim reference1 As AnyObject
Set reference1 = originElements1.PlaneXY

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(180.000000, 0.000000)

point2D1.ReportName = 3

Dim line2D3 As Line2D
Set line2D3 = factory2D1.CreateLine(0.000000, 0.000000, 180.000000, 0.000000)

line2D3.ReportName = 4

Dim point2D2 As CATBaseDispatch
Set point2D2 = axis2D1.GetItem("Origin")

line2D3.StartPoint = point2D2

line2D3.EndPoint = point2D1

Dim point2D3 As Point2D
Set point2D3 = factory2D1.CreatePoint(180.000000, 130.000000)

point2D3.ReportName = 5

Dim line2D4 As Line2D
Set line2D4 = factory2D1.CreateLine(180.000000, 0.000000, 180.000000, 130.000000)

line2D4.ReportName = 6

line2D4.StartPoint = point2D1

line2D4.EndPoint = point2D3

Dim point2D4 As Point2D
Set point2D4 = factory2D1.CreatePoint(-0.000000, 130.000000)

point2D4.ReportName = 7

Dim line2D5 As Line2D
Set line2D5 = factory2D1.CreateLine(180.000000, 130.000000, 0.000000, 130.000000)

line2D5.ReportName = 8

line2D5.StartPoint = point2D3

line2D5.EndPoint = point2D4

Dim line2D6 As Line2D
Set line2D6 = factory2D1.CreateLine(0.000000, 130.000000, 0.000000, 0.000000)

line2D6.ReportName = 9

line2D6.StartPoint = point2D4

line2D6.EndPoint = point2D2

Dim constraints1 As Constraints
Set constraints1 = sketch1.Constraints

Dim reference2 As Reference
Set reference2 = part1.CreateReferenceFromObject(line2D3)

Dim reference3 As Reference
Set reference3 = part1.CreateReferenceFromObject(line2D1)

Dim constraint1 As Constraint
Set constraint1 = constraints1.AddBiEltCst(catCstTypeHorizontality, reference2, reference3)

constraint1.Mode = catCstModeDrivingDimension

Dim reference4 As Reference
Set reference4 = part1.CreateReferenceFromObject(line2D5)

Dim reference5 As Reference
Set reference5 = part1.CreateReferenceFromObject(line2D1)

Dim constraint2 As Constraint
Set constraint2 = constraints1.AddBiEltCst(catCstTypeHorizontality, reference4, reference5)

constraint2.Mode = catCstModeDrivingDimension

Dim reference6 As Reference
Set reference6 = part1.CreateReferenceFromObject(line2D4)

Dim reference7 As Reference
Set reference7 = part1.CreateReferenceFromObject(line2D2)

Dim constraint3 As Constraint
Set constraint3 = constraints1.AddBiEltCst(catCstTypeVerticality, reference6, reference7)

constraint3.Mode = catCstModeDrivingDimension

Dim reference8 As Reference
Set reference8 = part1.CreateReferenceFromObject(line2D6)

Dim reference9 As Reference
Set reference9 = part1.CreateReferenceFromObject(line2D2)

Dim constraint4 As Constraint
Set constraint4 = constraints1.AddBiEltCst(catCstTypeVerticality, reference8, reference9)

constraint4.Mode = catCstModeDrivingDimension

Dim point2D5 As Point2D
Set point2D5 = factory2D1.CreatePoint(30.000000, 65.000000)

point2D5.ReportName = 10

Dim circle2D1 As Circle2D
Set circle2D1 = factory2D1.CreateClosedCircle(30.000000, 65.000000, 5.000000)

circle2D1.CenterPoint = point2D5

circle2D1.ReportName = 11

Dim point2D6 As Point2D
Set point2D6 = factory2D1.CreatePoint(45.000000, 80.000000)

point2D6.ReportName = 12

Dim circle2D2 As Circle2D
Set circle2D2 = factory2D1.CreateClosedCircle(45.000000, 80.000000, 5.000000)

circle2D2.CenterPoint = point2D6

circle2D2.ReportName = 13

Dim point2D7 As Point2D
Set point2D7 = factory2D1.CreatePoint(45.000000, 50.000000)

point2D7.ReportName = 14

Dim circle2D3 As Circle2D
Set circle2D3 = factory2D1.CreateClosedCircle(45.000000, 50.000000, 5.000000)

circle2D3.CenterPoint = point2D7

circle2D3.ReportName = 15

Dim point2D8 As Point2D
Set point2D8 = factory2D1.CreatePoint(150.000000, 65.000000)

point2D8.ReportName = 16

Dim circle2D4 As Circle2D
Set circle2D4 = factory2D1.CreateClosedCircle(150.000000, 65.000000, 5.000000)

circle2D4.CenterPoint = point2D8

circle2D4.ReportName = 17

Dim point2D9 As Point2D
Set point2D9 = factory2D1.CreatePoint(135.000000, 80.000000)

point2D9.ReportName = 18

Dim circle2D5 As Circle2D
Set circle2D5 = factory2D1.CreateClosedCircle(135.000000, 80.000000, 5.000000)

circle2D5.CenterPoint = point2D9

circle2D5.ReportName = 19

Dim point2D10 As Point2D
Set point2D10 = factory2D1.CreatePoint(135.000000, 50.000000)

point2D10.ReportName = 20

Dim circle2D6 As Circle2D
Set circle2D6 = factory2D1.CreateClosedCircle(135.000000, 50.000000, 5.000000)

circle2D6.CenterPoint = point2D10

circle2D6.ReportName = 21

sketch1.CloseEdition 

part1.InWorkObject = body1

part1.UpdateObject sketch1

part1.InWorkObject = body1

Dim shapeFactory1 As Factory
Set shapeFactory1 = part1.ShapeFactory

Dim pad1 As Pad
Set pad1 = shapeFactory1.AddNewPad(sketch1, 20.000000)

Dim limit1 As Limit
Set limit1 = pad1.FirstLimit

Dim length1 As Length
Set length1 = limit1.Dimension

length1.Value = 30.000000

part1.UpdateObject pad1

Dim product1 As CATBaseDispatch
Set product1 = partDocument1.GetItem("Part1")

product1.PartNumber = "Plate"

End Sub
