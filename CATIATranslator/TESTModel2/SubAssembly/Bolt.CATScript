Language="VBSCRIPT"

Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim reference1 As AnyObject
Set reference1 = originElements1.PlaneXY

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(7.000000, 0.000000)

point2D1.ReportName = 3

Dim line2D3 As Line2D
Set line2D3 = factory2D1.CreateLine(0.000000, 0.000000, 7.000000, 0.000000)

line2D3.ReportName = 4

Dim point2D2 As CATBaseDispatch
Set point2D2 = axis2D1.GetItem("Origin")

line2D3.StartPoint = point2D2

line2D3.EndPoint = point2D1

Dim constraints1 As Constraints
Set constraints1 = sketch1.Constraints

Dim reference2 As Reference
Set reference2 = part1.CreateReferenceFromObject(line2D3)

Dim reference3 As Reference
Set reference3 = part1.CreateReferenceFromObject(line2D1)

Dim constraint1 As Constraint
Set constraint1 = constraints1.AddBiEltCst(catCstTypeHorizontality, reference2, reference3)

constraint1.Mode = catCstModeDrivingDimension

Dim point2D3 As Point2D
Set point2D3 = factory2D1.CreatePoint(7.000000, 5.000000)

point2D3.ReportName = 5

Dim line2D4 As Line2D
Set line2D4 = factory2D1.CreateLine(7.000000, 0.000000, 7.000000, 5.000000)

line2D4.ReportName = 6

line2D4.StartPoint = point2D1

line2D4.EndPoint = point2D3

Dim reference4 As Reference
Set reference4 = part1.CreateReferenceFromObject(line2D4)

Dim reference5 As Reference
Set reference5 = part1.CreateReferenceFromObject(line2D2)

Dim constraint2 As Constraint
Set constraint2 = constraints1.AddBiEltCst(catCstTypeVerticality, reference4, reference5)

constraint2.Mode = catCstModeDrivingDimension

Dim point2D4 As Point2D
Set point2D4 = factory2D1.CreatePoint(5.000000, 5.000000)

point2D4.ReportName = 7

Dim line2D5 As Line2D
Set line2D5 = factory2D1.CreateLine(7.000000, 5.000000, 5.000000, 5.000000)

line2D5.ReportName = 8

line2D5.StartPoint = point2D3

line2D5.EndPoint = point2D4

Dim reference6 As Reference
Set reference6 = part1.CreateReferenceFromObject(line2D5)

Dim reference7 As Reference
Set reference7 = part1.CreateReferenceFromObject(line2D1)

Dim constraint3 As Constraint
Set constraint3 = constraints1.AddBiEltCst(catCstTypeHorizontality, reference6, reference7)

constraint3.Mode = catCstModeDrivingDimension

Dim point2D5 As Point2D
Set point2D5 = factory2D1.CreatePoint(5.000000, 50.000000)

point2D5.ReportName = 9

Dim line2D6 As Line2D
Set line2D6 = factory2D1.CreateLine(5.000000, 5.000000, 5.000000, 50.000000)

line2D6.ReportName = 10

line2D6.StartPoint = point2D4

line2D6.EndPoint = point2D5

Dim reference8 As Reference
Set reference8 = part1.CreateReferenceFromObject(line2D6)

Dim reference9 As Reference
Set reference9 = part1.CreateReferenceFromObject(line2D2)

Dim constraint4 As Constraint
Set constraint4 = constraints1.AddBiEltCst(catCstTypeVerticality, reference8, reference9)

constraint4.Mode = catCstModeDrivingDimension

Dim point2D6 As Point2D
Set point2D6 = factory2D1.CreatePoint(0.000000, 50.000000)

point2D6.ReportName = 11

Dim line2D7 As Line2D
Set line2D7 = factory2D1.CreateLine(5.000000, 50.000000, 0.000000, 50.000000)

line2D7.ReportName = 12

line2D7.StartPoint = point2D5

line2D7.EndPoint = point2D6

Dim reference10 As Reference
Set reference10 = part1.CreateReferenceFromObject(point2D6)

Dim reference11 As Reference
Set reference11 = part1.CreateReferenceFromObject(line2D2)

Dim constraint5 As Constraint
Set constraint5 = constraints1.AddBiEltCst(catCstTypeOn, reference10, reference11)

constraint5.Mode = catCstModeDrivingDimension

Dim reference12 As Reference
Set reference12 = part1.CreateReferenceFromObject(line2D7)

Dim reference13 As Reference
Set reference13 = part1.CreateReferenceFromObject(line2D1)

Dim constraint6 As Constraint
Set constraint6 = constraints1.AddBiEltCst(catCstTypeHorizontality, reference12, reference13)

constraint6.Mode = catCstModeDrivingDimension

Dim line2D8 As Line2D
Set line2D8 = factory2D1.CreateLine(0.000000, 50.000000, 0.000000, 0.000000)

line2D8.ReportName = 13

line2D8.StartPoint = point2D6

line2D8.EndPoint = point2D2

Dim reference14 As Reference
Set reference14 = part1.CreateReferenceFromObject(line2D8)

Dim reference15 As Reference
Set reference15 = part1.CreateReferenceFromObject(line2D2)

Dim constraint7 As Constraint
Set constraint7 = constraints1.AddBiEltCst(catCstTypeVerticality, reference14, reference15)

constraint7.Mode = catCstModeDrivingDimension

sketch1.CloseEdition 

part1.InWorkObject = body1

part1.UpdateObject sketch1

Dim shapeFactory1 As Factory
Set shapeFactory1 = part1.ShapeFactory

Dim shaft1 As Shaft
Set shaft1 = shapeFactory1.AddNewShaft(sketch1)

Dim parameters1 As Parameters
Set parameters1 = part1.Parameters

Dim length1 As Parameter
Set length1 = parameters1.Item("Part1\PartBody\Shaft.1\ThickThin1")

length1.Value = 1.000000

Dim parameters2 As Parameters
Set parameters2 = part1.Parameters

Dim length2 As Parameter
Set length2 = parameters2.Item("Part1\PartBody\Shaft.1\ThickThin2")

length2.Value = 0.000000

Dim reference16 As Reference
Set reference16 = part1.CreateReferenceFromBRepName("WireREdge:(Wire:(Brp:(Sketch.1;13);None:(Limits1:();Limits2:());Cf11:());WithTemporaryBody;WithoutBuildError;WithSelectingFeatureSupport;MFBRepVersion_CXR15)", sketch1)

shaft1.RevoluteAxis = reference16

part1.UpdateObject shaft1

Dim reference17 As Reference
Set reference17 = part1.CreateReferenceFromName("Selection_RSur:(Face:(Brp:(Shaft.1;0:(Brp:(Sketch.1;12)));None:();Cf11:());Shaft.1_ResultOUT;Z0;G4162)")

Dim sketch2 As Sketch
Set sketch2 = sketches1.Add(reference17)

Dim arrayOfVariantOfDouble2(8)
arrayOfVariantOfDouble2(0) = 0.000000
arrayOfVariantOfDouble2(1) = 50.000000
arrayOfVariantOfDouble2(2) = 0.000000
arrayOfVariantOfDouble2(3) = -1.000000
arrayOfVariantOfDouble2(4) = 0.000000
arrayOfVariantOfDouble2(5) = -0.000000
arrayOfVariantOfDouble2(6) = 0.000000
arrayOfVariantOfDouble2(7) = 0.000000
arrayOfVariantOfDouble2(8) = 1.000000
sketch2.SetAbsoluteAxisData arrayOfVariantOfDouble2

part1.InWorkObject = sketch2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D9 As CATBaseDispatch
Set line2D9 = axis2D2.GetItem("HDirection")

line2D9.ReportName = 1

Dim line2D10 As CATBaseDispatch
Set line2D10 = axis2D2.GetItem("VDirection")

line2D10.ReportName = 2

Dim point2D7 As Point2D
Set point2D7 = factory2D2.CreatePoint(-10.000000, 7.000000)

point2D7.ReportName = 3

Dim point2D8 As Point2D
Set point2D8 = factory2D2.CreatePoint(10.000000, 7.000000)

point2D8.ReportName = 4

Dim line2D11 As Line2D
Set line2D11 = factory2D2.CreateLine(-10.000000, 7.000000, 10.000000, 7.000000)

line2D11.ReportName = 5

line2D11.StartPoint = point2D7

line2D11.EndPoint = point2D8

Dim point2D9 As Point2D
Set point2D9 = factory2D2.CreatePoint(10.000000, -7.000000)

point2D9.ReportName = 6

Dim line2D12 As Line2D
Set line2D12 = factory2D2.CreateLine(10.000000, 7.000000, 10.000000, -7.000000)

line2D12.ReportName = 7

line2D12.EndPoint = point2D8

line2D12.StartPoint = point2D9

Dim point2D10 As Point2D
Set point2D10 = factory2D2.CreatePoint(-10.000000, -7.000000)

point2D10.ReportName = 8

Dim line2D13 As Line2D
Set line2D13 = factory2D2.CreateLine(10.000000, -7.000000, -10.000000, -7.000000)

line2D13.ReportName = 9

line2D13.StartPoint = point2D9

line2D13.EndPoint = point2D10

Dim line2D14 As Line2D
Set line2D14 = factory2D2.CreateLine(-10.000000, -7.000000, -10.000000, 7.000000)

line2D14.ReportName = 10

line2D14.EndPoint = point2D10

line2D14.StartPoint = point2D7

Dim constraints2 As Constraints
Set constraints2 = sketch2.Constraints

Dim reference18 As Reference
Set reference18 = part1.CreateReferenceFromObject(line2D11)

Dim reference19 As Reference
Set reference19 = part1.CreateReferenceFromObject(line2D9)

Dim constraint8 As Constraint
Set constraint8 = constraints2.AddBiEltCst(catCstTypeHorizontality, reference18, reference19)

constraint8.Mode = catCstModeDrivingDimension

Dim reference20 As Reference
Set reference20 = part1.CreateReferenceFromObject(line2D13)

Dim reference21 As Reference
Set reference21 = part1.CreateReferenceFromObject(line2D9)

Dim constraint9 As Constraint
Set constraint9 = constraints2.AddBiEltCst(catCstTypeHorizontality, reference20, reference21)

constraint9.Mode = catCstModeDrivingDimension

Dim reference22 As Reference
Set reference22 = part1.CreateReferenceFromObject(line2D12)

Dim reference23 As Reference
Set reference23 = part1.CreateReferenceFromObject(line2D10)

Dim constraint10 As Constraint
Set constraint10 = constraints2.AddBiEltCst(catCstTypeVerticality, reference22, reference23)

constraint10.Mode = catCstModeDrivingDimension

Dim reference24 As Reference
Set reference24 = part1.CreateReferenceFromObject(line2D14)

Dim reference25 As Reference
Set reference25 = part1.CreateReferenceFromObject(line2D10)

Dim constraint11 As Constraint
Set constraint11 = constraints2.AddBiEltCst(catCstTypeVerticality, reference24, reference25)

constraint11.Mode = catCstModeDrivingDimension

sketch2.CloseEdition 

part1.InWorkObject = shaft1

part1.UpdateObject sketch2

Dim pad1 As Pad
Set pad1 = shapeFactory1.AddNewPad(sketch2, 20.000000)

Dim limit1 As Limit
Set limit1 = pad1.FirstLimit

Dim length3 As Length
Set length3 = limit1.Dimension

length3.Value = 5.000000

part1.UpdateObject pad1

Dim product1 As CATBaseDispatch
Set product1 = partDocument1.GetItem("Part1")

product1.PartNumber = "Bolt"

End Sub
