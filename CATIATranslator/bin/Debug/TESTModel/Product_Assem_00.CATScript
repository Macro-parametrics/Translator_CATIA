Language="VBSCRIPT"
Sub CATMain()
Dim documents1 As Documents
Set documents1 = CATIA.Documents
Dim productDocument1 As Document
Set productDocument1 = documents1.Add("Product")
Dim product1 As Product
Set product1 = productDocument1.Product
Dim products1 As Products
Set products1 = product1.Products
Dim arrayOfVariantOfBSTR1(0)
arrayOfVariantOfBSTR1(0) = "C:\Users\Imgyu Kim\Documents\Visual Studio 2015\Repos\TransCATIA\TransCAT(C#)\CATIATranslator\bin\Debug\TESTmodel\Product_Part00.CATPart"
products1.AddComponentsFromFiles arrayOfVariantOfBSTR1, "All"
Dim arrayOfVariantOfBSTR2(0)
arrayOfVariantOfBSTR2(0) = "C:\Users\Imgyu Kim\Documents\Visual Studio 2015\Repos\TransCATIA\TransCAT(C#)\CATIATranslator\bin\Debug\TESTmodel\Product_Part01.CATPart"
products1.AddComponentsFromFiles arrayOfVariantOfBSTR2, "All"
Dim constraints1 As Collection
Set constraints1 = product1.Connections("CATIAConstraints")
Dim reference1 As Reference
Set reference1 = product1.CreateReferenceFromName("Product1/Part1.1/!Selection_RSur:(Face:(Brp:(Pad.1;1);None:();Cf11:());Pocket.1_ResultOUT;Z0;G4162)")
Dim reference2 As Reference
Set reference2 = product1.CreateReferenceFromName("Product1/Part1.2/!Selection_RSur:(Face:(Brp:(Pad.1;2);None:();Cf11:());Pad.2_ResultOUT;Z0;G4162)")
Dim constraint1 As Constraint
Set constraint1 = constraints1.AddBiEltCst(catCstTypeSurfContact, reference1, reference2)
product1.Update 
Set constraints1 = product1.Connections("CATIAConstraints")
Dim reference3 As Reference
Set reference3 = product1.CreateReferenceFromName("Product1/Part1.1/!Axis:(Selection_RSur:(Face:(Brp:(Pocket.1;0:(Brp:(Sketch.2;1)));None:();Cf11:());Pocket.1_ResultOUT;Z0;G4162))")
Dim reference4 As Reference
Set reference4 = product1.CreateReferenceFromName("Product1/Part1.2/!Axis:(Selection_RSur:(Face:(Brp:(Pad.2;0:(Brp:(Sketch.2;1)));None:();Cf11:());Pad.2_ResultOUT;Z0;G4162))")
Dim constraint2 As Constraint
Set constraint2 = constraints1.AddBiEltCst(catCstTypeOn, reference3, reference4)
product1.Update 
End Sub
